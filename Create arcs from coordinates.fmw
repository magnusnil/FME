FME workspace Create arcs from coordinates.fmw
Title: Create arcs from coordinates
Description: Create arcs from coordinates

Parameters:
- DestDataset_ESRISHAPE =
- SourceDataset_XLSXR =

Readers:
- XLSXR_1: XLSXR from $(SourceDataset_XLSXR) in EPSG:3006

Writers:
- ESRISHAPE_1: ESRISHAPE to $(DestDataset_ESRISHAPE) in EPSG:3006

Note: Task / Create arcs from coordinates / Data sets used / - Excel file with coordinates for start/end for each line / Magnus Nilsson / magnus.nilsson@vgregion.se

Bookmark: Input
Note: List of coordiate pairs
Sheet1 (reader XLSXR_1)
    attributes: ID number(2,0), StartNorth number(8,0), StartEast number(7,0), EndNorth number(8,0), EndEast number(7,0), Amount number(3,0), Area char(18)
    -> ExpressionEvaluator

Bookmark: Create coordinates for centre point
Note: Create CenterY
ExpressionEvaluator
    ACTION = Create New Attribute
    EXPRESSION = (@Value(StartNorth)+@Value(EndNorth))/2
    VAL_ATTR = CenterY
    -> ExpressionEvaluator_2
Note: Create CenterX
ExpressionEvaluator_2
    ACTION = Create New Attribute
    EXPRESSION = (@Value(StartEast)+@Value(EndEast))/2
    VAL_ATTR = CenterX
    -> AttributeCreator
Note: Create CenterZ
AttributeCreator
    ATTR_TABLE = SET_TO CenterZ = 25000
    -> VertexCreator
    -> VertexCreator_2
    -> VertexCreator_3

Bookmark: Manage geometries
Note: Create startpoint
VertexCreator
    MEASURE_TYPE = Continuous
    MISSING_VAL_MODE = None (Drop Values)
    MODE_NAME = Add Point
    XVAL = @Value(StartEast)
    YVAL = @Value(StartNorth)
    -> LineBuilder
Note: Create centrepoint
VertexCreator_2
    MEASURE_TYPE = Continuous
    MISSING_VAL_MODE = None (Drop Values)
    MODE_NAME = Add Point
    XVAL = @Value(CenterX)
    YVAL = @Value(CenterY)
    ZVAL = @Value(CenterZ)
    -> LineBuilder
Note: Create endpoint
VertexCreator_3
    MEASURE_TYPE = Continuous
    MISSING_VAL_MODE = None (Drop Values)
    MODE_NAME = Add Point
    XVAL = @Value(EndEast)
    YVAL = @Value(EndNorth)
    -> LineBuilder
Note: Create line for each feature
LineBuilder
    ACCUM_INPUT_ATTRS = Use Attributes From One Feature
    GROUP_BY = ID
    REMOVE_DUPLICATES = No
    LINE -> Generalizer
Note: Generalize lines
Generalizer
    ALG_TEXT = NURBfit (Smooth)
    DEGREE = 2
    PRESERVE = No
    PRESERVE_PATHS = No
    SEGMENT_LENGTH = 0
    -> CoordinateSystemSetter
Note: Set to EPSG 3006
CoordinateSystemSetter
    COORDSYS = EPSG:3006
    -> Lines (writer ESRISHAPE_1)

Bookmark: Output
Note: SHP
Lines (writer ESRISHAPE_1)
