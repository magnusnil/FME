FME workspace LEGO-map.fmw

Parameters:
- DestDataset_SHAPEFILE =
- SourceDataset_OGCGEOPACKAGE =
- SourceDataset_SHAPEFILE =

Readers:
- SHAPEFILE_1: SHAPEFILE from $(SourceDataset_SHAPEFILE) in EPSG:3006
- OGCGEOPACKAGE_1: OGCGEOPACKAGE from $(SourceDataset_OGCGEOPACKAGE) in EPSG:3006

Writers:
- SHAPEFILE_2: SHAPEFILE to $(DestDataset_SHAPEFILE) in EPSG:3006

Note: Task / Transform geodata for LEGO map / Inspired by https://maps.gisforthought.com/LegoIreland/ / Magnus Nilsson / magnus.nilsson@vgregion.se

Bookmark: Input
Note: Population grid, 1x1 km / SHP
Totalbefolkning_1km_201231 (reader OGCGEOPACKAGE_1)
    attributes: RutStorl mediumint, Ruta text(13), Pop mediumint
    -> AttributeManager
Note: Municipalities / SHP
ak_14 (reader SHAPEFILE_1)
    attributes: DETALJTYP char(10), ADAT char(16), LANKOD char(2), KOMMUNKOD char(4), KOMMUNNAMN char(16)
    -> AttributeFilter

Bookmark: Prepare population grid
Note: Remove a few attributes
AttributeManager
    ATTR_TABLE:
      REMOVE RutStorl
      REMOVE Ruta
      REMOVE _clipped
    -> Clipper [CLIPPEE]
Note: Filter municipalities
AttributeFilter
    ATTR_NAME = KOMMUNKOD
    ATTR_VALUES = <Empty>,<Missing>,<Null>,<Unfiltered>,1401,1402,1440,1441,1480,1481,1482
    1401 -> Dissolver
    1402 -> Dissolver
    1440 -> Dissolver
    1441 -> Dissolver
    1480 -> Dissolver
    1481 -> Dissolver
    1482 -> Dissolver
Note: Dissolve municipalities
Dissolver
    ACCUM_INPUT_ATTRS = Use Attributes From One Feature
    CLEANING_TOLERANCE = Automatic
    CONNECT_Z_MODE = First Wins
    DEAGGREGATE_INPUT = Yes
    AREA -> Clipper [CLIPPER]
Note: Clip population grid
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> AreaCalculator
Note: Calculate area for Tester
AreaCalculator
    AREA_ATTR = _area
    AREA_TYPE = Plane Area
    MULT = 1
    -> Tester
Note: Keep only 1x1 km polygons
Tester
    BOOL_OP = OR
    COMPOSITE_TEST = 1
    TEST_CLAUSE = TEST @Value(_area) = 1000000
    TEST_MODE = TEST
    PASSED -> ExpressionEvaluator
Note: Create "klosshojd" to set minimum height for LEGO pieces
ExpressionEvaluator
    ACTION = Create New Attribute
    EXPRESSION = @Value(Pop)+500
    VAL_ATTR = klosshojd
    -> CenterPointReplacer
    -> Extruder

Bookmark: Create LEGO pieces
Note: 2D -> staplar utifrån befolkning
Extruder
    DIRECTION = Auto
    DISTANCE = @Value(klosshojd)
    EXTRUDED -> LEGO pieces (writer SHAPEFILE_2)

Bookmark: Output
Note: LEGO pieces / SHP
LEGO pieces (writer SHAPEFILE_2)
    attributes: Pop long
Note: Buttons / SHP
Buttons (writer SHAPEFILE_2)
    attributes: Pop long

Bookmark: Create buttons on top of pieces
Note: Polygon -> center point
CenterPointReplacer
    POINTTYPE = CENTER
    POINT -> Bufferer
Note: Buffer for creating circles
Bufferer
    ANGLE = 22.5
    CAP_STYLE = Arc
    CORNER_STYLE = Arc
    MODE = AREA
    OFFSET = 350
    OFFSET_UNITS = NONE
    PRECISION = APPROX
    BUFFERED -> 3DForcer
Note: Set z level for buttons
3DForcer
    KEEPZVAL = No
    ZVALATTR = @Value(klosshojd)
    -> Extruder_2
Note: Circle -> button
Extruder_2
    DIRECTION = Auto
    DISTANCE = 200
    EXTRUDED -> Buttons (writer SHAPEFILE_2)
