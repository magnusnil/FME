FME workspace Calculate population for health care clinics.fmw
Title: Calculate population for health care clinics
Description: Calculate population within 5 km (as the crow flies) from each health care clinic

Parameters:
- DestDataset_SHAPEFILE =
- SourceDataset_OGCGEOPACKAGE =
- SourceDataset_OGCGEOPACKAGE_3 =
- SourceDataset_SHAPEFILE =

Readers:
- OGCGEOPACKAGE_1: OGCGEOPACKAGE from $(SourceDataset_OGCGEOPACKAGE) in EPSG:3006
- SHAPEFILE_1: SHAPEFILE from $(SourceDataset_SHAPEFILE) in EPSG:3006
- OGCGEOPACKAGE_2: OGCGEOPACKAGE from $(SourceDataset_OGCGEOPACKAGE_3) in EPSG:3006

Writers:
- SHAPEFILE_2: SHAPEFILE to $(DestDataset_SHAPEFILE) in EPSG:3006

Note: Task / Calculate population within 5 km (as the crow flies) from each health care clinic / Data sets used / - Health care clinics: Vårdcentraler i Vårdval vårdcentral - Sveriges dataportal / - Municipalities: Översiktskartan, https://www.lantmateriet.se/sv/Kartor-och-geografisk-information/geodataprodukter/produktlista/oversiktskartan/ / - Population (1x1 km polygons): Statistik på rutor (scb.se) / Magnus Nilsson / magnus.nilsson@vgregion.se

Bookmark: Input
Note: Population, 1x1 km grid / GeoPackage / About 114 000 feautres
totalbefolkning_1km_191231 (reader OGCGEOPACKAGE_2)
    attributes: rutstorl mediumint, ruta text(13), pop mediumint
    -> CenterPointReplacer
Note: Health care clinics / GeoPackage / 208 features
Vardval vardcentral vardcentraler (reader OGCGEOPACKAGE_1)
    attributes: hsaid text(200), namn text(200), foretag text(200), adress text(200), postnummer int, postort text(100)
    -> Bufferer
Note: Municipalities in Sweden / SHP / 328 features
ak_riks (reader SHAPEFILE_1)
    attributes: KOMMUNNAMN char(30), KKOD long, KATEGORI char(50), LANSNAMN char(30), KOMMUNKOD short, LANSKOD short, KOM_KOD char(4), LAN_KOD char(2), ADAT char(16)
    -> AttributeFilter

Bookmark: Calculate polulation within 5 km from each healt care clinics
Note: Polygons -> points
CenterPointReplacer
    POINTTYPE = CENTER
    POINT -> Clipper [CLIPPEE]
Note: Buffer 5 km
Bufferer
    ANGLE = 22.5
    CAP_STYLE = Arc
    CORNER_STYLE = Arc
    MODE = AREA
    OFFSET = 5000
    OFFSET_UNITS = NONE
    PRECISION = APPROX
    BUFFERED -> PointOnAreaOverlayer [AREA]
Note: Filter Västra Götaland
AttributeFilter
    ATTR_NAME = LANSKOD
    ATTR_VALUES = <Empty>,<Missing>,<Null>,<Unfiltered>,14
    14 -> Dissolver
Note: Dissolve municipalities
Dissolver
    ACCUM_INPUT_ATTRS = Use Attributes From One Feature
    CLEANING_TOLERANCE = Automatic
    CONNECT_Z_MODE = First Wins
    DEAGGREGATE_INPUT = Yes
    AREA -> Clipper [CLIPPER]
Note: Clip points outside of / Västra Götaland
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> PointOnAreaOverlayer [POINT]
Note: Fetch populations statistics, create list
PointOnAreaOverlayer
    ATTR_ACCUM_MODE = Merge Incoming
    ATTR_CONFLICT_RES = Use Original
    CANDIDATE_LIST_ATTRS_TO_INCLUDE = pop
    CANDIDATE_LIST_ATTRS_TO_INCLUDE_MODE = Selected Attributes
    CANDIDATE_LIST_NAME = lista
    DEAGGREGATE_INPUT = Yes
    LIST_ATTRS_TO_INCLUDE = namn
    LIST_NAME = lista
    OV_ATTR = _overlaps
    POLYS_FIRST = NO
    AREA -> ListSummer
Note: Sum list with population statistics
ListSummer
    RESULT = bef_sum
    SRC_LIST = lista{}.pop
    -> AttributeManager
Note: Manage attributes
AttributeManager
    ATTR_TABLE:
      REMOVE rutstorl
      REMOVE ruta
      REMOVE pop
      REMOVE _clipped
      REMOVE lista{}.pop
      REMOVE _overlaps
    -> VC med bef (writer SHAPEFILE_2)

Bookmark: Output
Note: Health care clinics / SHP
VC med bef (writer SHAPEFILE_2)
    attributes: hsaid char(200), namn char(200), foretag char(200), adress char(200), postnummer number(20,0), postort char(100), bef_sum short
